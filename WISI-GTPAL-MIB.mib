WISI-GTPAL-MIB DEFINITIONS ::= BEGIN
--============================================================================--

IMPORTS
	MODULE-COMPLIANCE, OBJECT-GROUP
		FROM SNMPv2-CONF

	MODULE-IDENTITY, NOTIFICATION-TYPE, OBJECT-TYPE,
	Unsigned32, Integer32
		FROM SNMPv2-SMI

	FloatingPoint
		FROM WISI-TANGRAM-MIB

	RowStatus, DisplayString
		FROM SNMPv2-TC

	gtModule, gtChannel
		FROM WISI-GTMODULES-MIB

	gtRF
		FROM WISI-TANGRAM-MIB;

--------------------------------------------------------------------------------

gtPALMIB MODULE-IDENTITY
	LAST-UPDATED "201609080000Z"
	ORGANIZATION "WISI Communications GmbH & Co. KG"
	CONTACT-INFO
		"https://wisiconnect.tv/"
	DESCRIPTION
		"This MIB module represents the PAL video interfaces in a
		system (rack unit) of a WISI next-generation headend. It
		provides configuration and measurement information for these
		interfaces."

	REVISION "201609080000Z"
	DESCRIPTION
		"Removed out channels and out FIFO objects. Changed the mono
		and stereo audio sub-carrier objects to have both configured
		and actual values. Updated contact information and module
		description."
	REVISION "201212121320Z"
	DESCRIPTION
		"Updated contact details."
	REVISION "201212041200Z"
	DESCRIPTION
		"Adjusted for Chameleon"
	REVISION "201112191200Z"
	DESCRIPTION
		"Initial version."
::= { gtRF 5 }

--------------------------------------------------------------------------------

gtPALNotifications OBJECT IDENTIFIER ::= { gtPALMIB 0 }
gtPALObjects OBJECT IDENTIFIER ::= { gtPALMIB 1 }
gtPALConformance OBJECT IDENTIFIER ::= { gtPALMIB 2 }
gtPALCompliances OBJECT IDENTIFIER ::= { gtPALConformance 1 }
gtPALGroups OBJECT IDENTIFIER ::= { gtPALConformance 2 }

--============================================================================--

gtPALNotifyLevelChanged NOTIFICATION-TYPE
	OBJECTS { gtPALoutLevel }
	STATUS current
	DESCRIPTION
		"The gtPALNotifyLevelChanged notification indicates that
		the carrier level of the PAL output has changed."
::= { gtPALNotifications 1 }

--============================================================================--

gtPALoutTable OBJECT-TYPE
	SYNTAX SEQUENCE OF GtPALoutEntry
	MAX-ACCESS not-accessible
	STATUS current
	DESCRIPTION
		"The gtPALoutTable table contains a list of all
		PAL audio channels within the GT01/GN50 rack unit."
::= { gtPALObjects 4 }

gtPALoutEntry OBJECT-TYPE
	SYNTAX GtPALoutEntry
	MAX-ACCESS not-accessible
	STATUS current
	DESCRIPTION
		"The gtPALoutEntry table entry represents an
		PAL audio channel within the GT01/GN50 rack unit."
	INDEX {
		gtModule,
		gtChannel
	}
::= { gtPALoutTable 1 }

GtPALoutEntry ::= SEQUENCE {
	gtPALoutRowStatus RowStatus,
	gtPALoutConnector Unsigned32,
        gtPALoutEnable INTEGER,
        gtPALoutDecoder OBJECT IDENTIFIER,
	gtPALoutConfigLevel Unsigned32,
        gtPALoutLevel FloatingPoint,
	gtPALoutFrequency Unsigned32,
	gtPALoutVideoStandard INTEGER,
	gtPALoutVideoSystem INTEGER,
	gtPALoutGroupDelayPre INTEGER,
	gtPALoutSecamVertialIdent INTEGER,
	gtPALoutTestLines INTEGER,
	gtPALoutVideoBandwidth INTEGER,
	gtPALoutVideoModulationDepth Unsigned32,
	gtPALoutAudioSystem INTEGER,
	gtPALoutAudioDualMono INTEGER,
	gtPALoutAudioMonoSCConfigLevel Integer32,
	gtPALoutAudioStereoSCConfigLevel Integer32,
	gtPALoutAudioDeviation Integer32,
	gtPALoutAudioMonoSCLevel Integer32,
	gtPALoutAudioStereoSCLevel Integer32
}

gtPALoutRowStatus OBJECT-TYPE
	SYNTAX RowStatus
	MAX-ACCESS read-create
	STATUS current
	DESCRIPTION
		"The gtPALoutRowStatus entity represents the row/entry status
		of a PAL audio channel within the GT01/GN50 rack unit."
::= { gtPALoutEntry 1 }

gtPALoutConnector OBJECT-TYPE
	SYNTAX Unsigned32
	MAX-ACCESS read-only
	STATUS current
	DESCRIPTION
		"The gtPALoutConnector entity represents related RF connector
		of a PAL audio channel within the GT01/GN50 rack unit."
::= { gtPALoutEntry 2 }

gtPALoutEnable OBJECT-TYPE
	SYNTAX INTEGER { disabled(1), active(2) }
	MAX-ACCESS read-write
	STATUS current
	DESCRIPTION
		"The gtPALoutEnable entity represents the enable setting
		of a PAL channel within the GT01/GN50 rack unit."
::= { gtPALoutEntry 3 }

gtPALoutDecoder OBJECT-TYPE
	SYNTAX OBJECT IDENTIFIER
	MAX-ACCESS read-only
	STATUS current
	DESCRIPTION
		"The gtPALoutDecoder referer to the settings table specific
                to the decoder used by the current PAL output on a SFM/MFM module."
::= { gtPALoutEntry 4 }

gtPALoutConfigLevel OBJECT-TYPE
	SYNTAX Unsigned32 (1..1000)
	UNITS "1/10 dBuV"
	MAX-ACCESS read-write
	STATUS current
	DESCRIPTION
		"The gtPALoutConfigLevel entity represents the configured
		output level of a PAL channel within the GT01/GN50 rack unit."
::= { gtPALoutEntry 5 }

gtPALoutLevel OBJECT-TYPE
	SYNTAX FloatingPoint
	UNITS "dBuV"
	MAX-ACCESS read-only
	STATUS current
	DESCRIPTION
		"The gtPALoutLevel entity represents the measured RF level
		of a PAL channel within the GT01/GN50 rack unit."
::= { gtPALoutEntry 6 }

gtPALoutFrequency OBJECT-TYPE
	SYNTAX Unsigned32 (87500..108000)
	UNITS "kHz"
	MAX-ACCESS read-write
	STATUS current
	DESCRIPTION
		"The gtPALoutFrequency entity represents the output frequency
		of a PAL channel within the GT01/GN50 rack unit."
::= { gtPALoutEntry 8 }

gtPALoutVideoStandard OBJECT-TYPE
	SYNTAX INTEGER { pal625(1), pal525(2), secam(3), ntsc(4) }
	MAX-ACCESS read-write
	STATUS current
	DESCRIPTION
		"The gtPALoutVideoStandard entity represents the video standard
		setting	of a PAL channel within the GT01/GN50 rack unit."
::= { gtPALoutEntry 10 }

gtPALoutVideoSystem OBJECT-TYPE
	SYNTAX INTEGER { bg(1), bh(2), dk(3), i(4), l(5), mn(6) }
	MAX-ACCESS read-write
	STATUS current
	DESCRIPTION
		"The gtPALoutVideoSystem entity represents the video system
		setting of a PAL channel within the GT01/GN50 rack unit."
::= { gtPALoutEntry 11 }

gtPALoutGroupDelayPre OBJECT-TYPE
	SYNTAX INTEGER { none(1), bgGeneral(2), bgGeneralHalf(3), dkGost20532-75(4), fcc(5) }
	MAX-ACCESS read-write
	STATUS current
	DESCRIPTION
		"The gtPALoutGroupDelayPre entity represents the group delay
		of a PAL channel within the GT01/GN50 rack unit."
::= { gtPALoutEntry 12 }

gtPALoutSecamVertialIdent OBJECT-TYPE
	SYNTAX INTEGER { disabled(1), active(2) }
	MAX-ACCESS read-write
	STATUS current
	DESCRIPTION
		"The gtPALoutSecamVertialIdent entity represents the
		setting if vertical identification should be enabled for SECAM
		of a PAL channel within the GT01/GN50 rack unit."
::= { gtPALoutEntry 13 }

gtPALoutTestLines OBJECT-TYPE
	SYNTAX INTEGER { disabled(1), active(2) }
	MAX-ACCESS read-write
	STATUS current
	DESCRIPTION
		"The gtPALoutTestLines entity represents the setting if
		PAL/SECAM test lines (17-19 + 330-332) should be enabled for
		SECAM of a PAL channel within the GT01/GN50 rack unit."
::= { gtPALoutEntry 14 }

gtPALoutVideoBandwidth OBJECT-TYPE
	SYNTAX INTEGER { bw4200kHz(4200), bw5000kHz(5000), bw6000kHz(6000) }
	MAX-ACCESS read-write
	STATUS current
	DESCRIPTION
		"The gtPALoutVideoBandwidth entity represents the forced setting
		of the video bandwidth of a PAL channel within the GT01/GN50 rack unit."
::= { gtPALoutEntry 15 }

gtPALoutVideoModulationDepth OBJECT-TYPE
	SYNTAX Unsigned32 (0..100)
	UNITS "%"
	MAX-ACCESS read-write
	STATUS current
	DESCRIPTION
		"The gtPALoutVideoModulationDepth entity represents the forced
		modulation depth of a PAL channel within the GT01/GN50 rack unit."
::= { gtPALoutEntry 16 }

gtPALoutAudioSystem OBJECT-TYPE
	SYNTAX INTEGER { nicam(1), a2stereo(2), a2stereostar(3), mono(4) }
	MAX-ACCESS read-write
	STATUS current
	DESCRIPTION
		"The gtPALoutAudioSystem entity represents the audio system
		setting of a PAL channel within the GT01/GN50 rack unit."
::= { gtPALoutEntry 20 }

gtPALoutAudioDualMono OBJECT-TYPE
	SYNTAX INTEGER { disabled(1), active(2) }
	MAX-ACCESS read-write
	STATUS current
	DESCRIPTION
		"The gtPALoutAudioDualMono entity represents the audio dual mono
		setting of a PAL channel within the GT01/GN50 rack unit."
::= { gtPALoutEntry 21 }

gtPALoutAudioMonoSCConfigLevel OBJECT-TYPE
	SYNTAX Integer32 (-1|0|10..30)
	UNITS "dBc"
	MAX-ACCESS read-write
	STATUS current
	DESCRIPTION
		"The gtPALoutAudioMonoSCConfigLevel entity represents the
		configured mono subcarrier level (relative to the carrier) of a
		PAL channel within the GT01/GN50 rack unit. A value of -1 means
		'auto' and 0 means that the subcarrier is disabled."
::= { gtPALoutEntry 22 }

gtPALoutAudioStereoSCConfigLevel OBJECT-TYPE
	SYNTAX Integer32 (-1|0|10..30)
	UNITS "dBc"
	MAX-ACCESS read-write
	STATUS current
	DESCRIPTION
		"The gtPALoutAudioStereoSCConfigLevel entity represents the
		configured stereo subcarrier level (relative to the carrier) of
		a PAL channel within the GT01/GN50 rack unit. A value of -1
		means 'auto' and 0 means that the subcarrier is disabled."
::= { gtPALoutEntry 23 }

gtPALoutAudioDeviation OBJECT-TYPE
	SYNTAX Integer32 (-6..6)
	UNITS "dB"
	MAX-ACCESS read-write
	STATUS current
	DESCRIPTION
		"The gtPALoutAudioDeviation entity represents the audio deviation
		setting of a PAL channel within the GT01/GN50 rack unit."
::= { gtPALoutEntry 25 }

gtPALoutAudioMonoSCLevel OBJECT-TYPE
	SYNTAX Integer32 (0|10..30)
	UNITS "dBc"
	MAX-ACCESS read-only
	STATUS current
	DESCRIPTION
		"The gtPALoutAudioMonoSCLevel entity represents the current
		mono subcarrier level (relative to the carrier) of a PAL
		channel within the GT01/GN50 rack unit. A value of 0 means that
		the subcarrier is disabled."
::= { gtPALoutEntry 26 }

gtPALoutAudioStereoSCLevel OBJECT-TYPE
	SYNTAX Integer32 (0|10..30)
	UNITS "dBc"
	MAX-ACCESS read-only
	STATUS current
	DESCRIPTION
		"The gtPALoutAudioStereoSCLevel entity represents the current
		stereo subcarrier level (relative to the carrier) of a PAL
		channel within the GT01/GN50 rack unit. A value of 0 means that
		the subcarrier is disabled."
::= { gtPALoutEntry 27 }

--============================================================================--

--gtPALMIBCompliance MODULE-COMPLIANCE
--	STATUS current
--	DESCRIPTION
--		"The compliance statement for GTPALv2 entities
--		which implement the GTPALv2 MIB."
--	MODULE
--	MANDATORY-GROUPS {
--		gtPALV1Group,
--		gtPALSystemGroup,
--		gtPALStatsGroup,
--		gtPALTrapGroup,
--		gtPALSetGroup,
--		gtPALBasicNotificationsGroup
--	}
--::= { gtPALCompliances 1 }

--------------------------------------------------------------------------------

--gtPALV1Group OBJECT-GROUP
--	OBJECTS {
--		gtPALoutRowStatus,
--		gtPALoutConnector,
--		gtPALoutLevel,
--		gtPALoutAttenuation,
--		gtPALoutEnable,
--		gtPALoutFrequency,
--		gtPALoutRatioSC1,
--		gtPALoutRatioSC2,
--		gtPALoutGroupDelayPre,
--		gtPALoutSID,
--		gtPALoutPMTPID,
--		gtPALoutPCRPID,
--		gtPALoutAudioMode,
--		gtPALoutTVMode,
--		gtPALoutVideoPID,
--		gtPALoutResolutionH,
--		gtPALoutResolutionV,
--		gtPALoutAspectRatio,
--		gtPALoutScanType,
--		gtPALoutRefreshRate,
--		gtPALoutSubtitles,
--		gtPALoutSubtitlePID,
--		gtPALoutSubtitlePage,
--		gtPALoutTeletextPID,
--		gtPALoutAudioPID,
--		gtPALoutAudioGain,
--		gtPALoutAudioSampleRate,
--		gtPALoutAudioBitRate,
--		gtPALoutAudioCodecState,
--		gtPALoutAudioCodecError,
--		gtPALoutAudioDeviation,
--		gtPALoutAudioClipping,
--		gtPALoutAudioPreemphasis
--	}
--	STATUS current
--	DESCRIPTION
--		"The gtPALV1Group group is mandatory only for those
--		GTPALv2 entities which also implement GTPALv1."
--::= { gtPALGroups 1 }

--------------------------------------------------------------------------------

--gtPALSystemGroup OBJECT-GROUP
--	OBJECTS {
--		gtPALoutRowStatus,
--		gtPALoutConnector,
--		gtPALoutLevel,
--		gtPALoutAttenuation,
--		gtPALoutEnable,
--		gtPALoutFrequency,
--		gtPALoutRatioSC1,
--		gtPALoutRatioSC2,
--		gtPALoutGroupDelayPre,
--		gtPALoutSID,
--		gtPALoutPMTPID,
--		gtPALoutPCRPID,
--		gtPALoutAudioMode,
--		gtPALoutTVMode,
--		gtPALoutVideoPID,
--		gtPALoutResolutionH,
--		gtPALoutResolutionV,
--		gtPALoutAspectRatio,
--		gtPALoutScanType,
--		gtPALoutRefreshRate,
--		gtPALoutSubtitles,
--		gtPALoutSubtitlePID,
--		gtPALoutSubtitlePage,
--		gtPALoutTeletextPID,
--		gtPALoutAudioPID,
--		gtPALoutAudioGain,
--		gtPALoutAudioSampleRate,
--		gtPALoutAudioBitRate,
--		gtPALoutAudioCodecState,
--		gtPALoutAudioCodecError,
--		gtPALoutAudioDeviation,
--		gtPALoutAudioClipping,
--		gtPALoutAudioPreemphasis
--	}
--	STATUS current
--	DESCRIPTION
--		"The gtPALSystemGroup group defines GTPALv2
--		entities which are mandatory."
-- ::= { gtPALGroups 2 }

--------------------------------------------------------------------------------

-- gtPALStatsGroup OBJECT-GROUP
--	OBJECTS {
--		gtPALoutRowStatus,
--		gtPALoutConnector,
--		gtPALoutLevel,
--		gtPALoutAttenuation,
--		gtPALoutEnable,
--		gtPALoutFrequency,
--		gtPALoutRatioSC1,
--		gtPALoutRatioSC2,
--		gtPALoutGroupDelayPre,
-- 		gtPALoutSID,
-- 		gtPALoutPMTPID,
-- 		gtPALoutPCRPID,
-- 		gtPALoutAudioMode,
-- 		gtPALoutTVMode,
-- 		gtPALoutVideoPID,
-- 		gtPALoutResolutionH,
-- 		gtPALoutResolutionV,
-- 		gtPALoutAspectRatio,
-- 		gtPALoutScanType,
-- 		gtPALoutRefreshRate,
-- 		gtPALoutSubtitles,
-- 		gtPALoutSubtitlePID,
-- 		gtPALoutSubtitlePage,
-- 		gtPALoutTeletextPID,
-- 		gtPALoutAudioPID,
-- 		gtPALoutAudioGain,
-- 		gtPALoutAudioSampleRate,
-- 		gtPALoutAudioBitRate,
-- 		gtPALoutAudioCodecState,
-- 		gtPALoutAudioCodecError,
-- 		gtPALoutAudioDeviation,
-- 		gtPALoutAudioClipping,
-- 		gtPALoutAudioPreemphasis
-- 	}
-- 	STATUS current
-- 	DESCRIPTION
-- 		"The gtPALStatsGroup group defines GTPALv2
-- 		entities which provide statistical information."
-- ::= { gtPALGroups 3 }

--------------------------------------------------------------------------------

-- gtPALTrapGroup OBJECT-GROUP
-- 	OBJECTS {
-- 		gtPALoutLevel,
-- 		gtPALoutResolutionH,
-- 		gtPALoutResolutionV,
-- 		gtPALoutAspectRatio,
-- 		gtPALoutScanType,
-- 		gtPALoutRefreshRate
-- 	}
-- 	STATUS current
-- 	DESCRIPTION
-- 		"The gtPALTrapGroup group defines GTPALv2
-- 		trap objects which are mandatory."
-- ::= { gtPALGroups 4 }

--------------------------------------------------------------------------------

-- gtPALSetGroup OBJECT-GROUP
-- 	OBJECTS {
-- 		gtPALoutRowStatus,
-- 		gtPALoutAttenuation,
-- 		gtPALoutEnable,
-- 		gtPALoutFrequency,
-- 		gtPALoutRatioSC1,
-- 		gtPALoutRatioSC2,
-- 		gtPALoutGroupDelayPre,
-- 		gtPALoutSID,
-- 		gtPALoutPMTPID,
-- 		gtPALoutPCRPID,
-- 		gtPALoutAudioMode,
-- 		gtPALoutTVMode,
-- 		gtPALoutVideoPID,
-- 		gtPALoutSubtitles,
-- 		gtPALoutSubtitlePID,
-- 		gtPALoutSubtitlePage,
-- 		gtPALoutTeletextPID,
-- 		gtPALoutAudioPID,
-- 		gtPALoutAudioGain
-- 	}
-- 	STATUS current
-- 	DESCRIPTION
-- 		"The gtPALSetGroup group defines GTPALv2
-- 		entities which can be set the manager."
-- ::= { gtPALGroups 5 }

--------------------------------------------------------------------------------

--gtPALBasicNotificationsGroup OBJECT IDENTIFIER - NOTIFICATION-GROUP
--	NOTIFICATIONS {
--		gtPALNotifyNewIPv4Multicast
--	}
--	STATUS current
--	DESCRIPTION
--		"The gtPALBasicNotificationsGroup group defines
--		GTPALv2 notification objects which are mandatory."
--::= { gtPALGroups 6 }

--============================================================================--
END
