WISI-GTDVBS2-MIB DEFINITIONS ::= BEGIN
--============================================================================--

IMPORTS
	MODULE-COMPLIANCE, OBJECT-GROUP
		FROM SNMPv2-CONF

	MODULE-IDENTITY, NOTIFICATION-TYPE, OBJECT-TYPE,
	IpAddress, Unsigned32
		FROM SNMPv2-SMI

	FloatingPoint
		FROM WISI-TANGRAM-MIB

	RowStatus
		FROM SNMPv2-TC

	gtModule, gtChannel
		FROM WISI-GTMODULES-MIB

	gtDVB
		FROM WISI-TANGRAM-MIB;

--------------------------------------------------------------------------------

gtDVBS2MIB MODULE-IDENTITY
	LAST-UPDATED "201609080000Z"
	ORGANIZATION "WISI Communications GmbH & Co. KG"
	CONTACT-INFO
		"https://wisiconnect.tv/"
	DESCRIPTION
		"This MIB module represents the DVB-S2 streaming interfaces in a
		system (rack unit) of a WISI next-generation headend. It
		provides configuration and measurement information for these
		interfaces."

	REVISION "201609080000Z"
	DESCRIPTION
		"Removed in channels and in enable objects. Updated contact
		information and module description."
	REVISION "201212121320Z"
	DESCRIPTION
		"Updated contact details."
	REVISION "201210311200Z"
	DESCRIPTION
		"Initial version."
::= { gtDVB 4 }

--------------------------------------------------------------------------------

gtDVBS2Notifications OBJECT IDENTIFIER ::= { gtDVBS2MIB 0 }
gtDVBS2Objects OBJECT IDENTIFIER ::= { gtDVBS2MIB 1 }
gtDVBS2Conformance OBJECT IDENTIFIER ::= { gtDVBS2MIB 2 }
gtDVBS2Compliances OBJECT IDENTIFIER ::= { gtDVBS2Conformance 1 }
gtDVBS2Groups OBJECT IDENTIFIER ::= { gtDVBS2Conformance 2 }

--============================================================================--

gtDVBS2NotifyLockedChanged NOTIFICATION-TYPE
	OBJECTS { gtDVBS2inLocked }
	STATUS current
	DESCRIPTION
		"The gtDVBS2NotifyLockedChanged notification indicates that
		the tuner locked status has changed."
::= { gtDVBS2Notifications 1 }

--============================================================================--

gtDVBS2inTable OBJECT-TYPE
	SYNTAX SEQUENCE OF GtDVBS2inEntry
	MAX-ACCESS not-accessible
	STATUS current
	DESCRIPTION
		"The gtDVBS2inTable table contains a list of all
		DVB-S2 input streams within the GT01/GN50 rack unit."
::= { gtDVBS2Objects 2 }

gtDVBS2inEntry OBJECT-TYPE
	SYNTAX GtDVBS2inEntry
	MAX-ACCESS not-accessible
	STATUS current
	DESCRIPTION
		"The gtDVBS2inEntry table entry represents an
		DVB-S2 input stream within the GT01/GN50 rack unit."
	INDEX {
		gtModule,
		gtChannel
	}
::= { gtDVBS2inTable 1 }

GtDVBS2inEntry ::= SEQUENCE {
	gtDVBS2inRowStatus RowStatus,
	gtDVBS2inConnector Unsigned32,
	gtDVBS2inLocked INTEGER,
	gtDVBS2inLevel FloatingPoint,
	gtDVBS2inSNR FloatingPoint,
	gtDVBS2inBER FloatingPoint,
	gtDVBS2inFrequency Unsigned32,
	gtDVBS2inPolarisation INTEGER,
	gtDVBS2inSymbolRate Unsigned32,
	gtDVBS2inModulation INTEGER,
	gtDVBS2inCodeRate INTEGER,
	gtDVBS2inLNBType INTEGER,
	gtDVBS2inLOFrequency Unsigned32,
	gtDVBS2inLNBVoltage INTEGER,
	gtDVBS2in22kHzTone INTEGER,
	gtDVBS2inDiSEqCType INTEGER,
	gtDVBS2inDiSEqCSource Unsigned32
}

gtDVBS2inRowStatus OBJECT-TYPE
	SYNTAX RowStatus
	MAX-ACCESS read-create
	STATUS current
	DESCRIPTION
		"The gtDVBS2inRowStatus entity represents the row/entry status
		of an DVB-S2 input stream within the GT01/GN50 rack unit."
::= { gtDVBS2inEntry 1 }

gtDVBS2inConnector OBJECT-TYPE
	SYNTAX Unsigned32 (1..4)
	UNITS "Connector"
	MAX-ACCESS read-only
	STATUS current
	DESCRIPTION
		"The gtDVBS2inConnector entity represents the ID of the physical
		connector used for a DVB-S2 input stream within the GT01/GN50 rack unit."
::= { gtDVBS2inEntry 2 }

gtDVBS2inLocked OBJECT-TYPE
	SYNTAX INTEGER { unlocked(1), locked(2) }
	MAX-ACCESS read-only
	STATUS current
	DESCRIPTION
		"The gtDVBS2inLocked entity represent the locked status
		of a DVB-S2 input stream within the GT01/GN50 rack unit."
::= { gtDVBS2inEntry 3 }

gtDVBS2inLevel OBJECT-TYPE
	SYNTAX FloatingPoint
	UNITS "dBm"
	MAX-ACCESS read-only
	STATUS current
	DESCRIPTION
		"The gtDVBS2inLevel entity represent the current RF level
		of a DVB-S2 input stream within the GT01/GN50 rack unit."
::= { gtDVBS2inEntry 4 }

gtDVBS2inSNR OBJECT-TYPE
	SYNTAX FloatingPoint
	UNITS "dB"
	MAX-ACCESS read-only
	STATUS current
	DESCRIPTION
		"The gtDVBS2inSNR entity represent the Signal to Noise Ratio
		of a DVB-S2 input stream within the GT01/GN50 rack unit."
::= { gtDVBS2inEntry 5 }

gtDVBS2inBER OBJECT-TYPE
	SYNTAX FloatingPoint
	MAX-ACCESS read-only
	STATUS current
	DESCRIPTION
		"The gtDVBS2inSNR entity represent the Signal to Noise Ratio
		of a DVB-S2 input stream within the GT01/GN50 rack unit."
::= { gtDVBS2inEntry 7 }

gtDVBS2inFrequency OBJECT-TYPE
	SYNTAX Unsigned32
	UNITS "kHz"
	MAX-ACCESS read-write
	STATUS current
	DESCRIPTION
		"The gtDVBS2inFrequency entity represent the frequency setting
		of a DVB-S2 input stream within the GT01/GN50 rack unit."
::= { gtDVBS2inEntry 11 }

gtDVBS2inPolarisation OBJECT-TYPE
	SYNTAX INTEGER { horizontal(1), vertical(2), circular-left(3), circular-right(4) }
	MAX-ACCESS read-write
	STATUS current
	DESCRIPTION
		"The gtDVBS2inPolarisation entity represent the signal polarisation
		of a DVB-S2 input stream within the GT01/GN50 rack unit."
::= { gtDVBS2inEntry 12 }

gtDVBS2inSymbolRate OBJECT-TYPE
	SYNTAX Unsigned32
	UNITS "Bd"
	MAX-ACCESS read-write
	STATUS current
	DESCRIPTION
		"The gtDVBS2inSymbolRate entity represent the symbolrate (in baud)
		of a DVB-S2 input stream within the GT01/GN50 rack unit."
::= { gtDVBS2inEntry 13 }

gtDVBS2inModulation OBJECT-TYPE
	SYNTAX INTEGER { auto(1), modqpsk(4), mod8psk(8), mod16qam(16) }
	MAX-ACCESS read-write
	STATUS current
	DESCRIPTION
		"The gtDVBS2inModulation entity represent the modulation
		of a DVB-S2 input stream within the GT01/GN50 rack unit."
::= { gtDVBS2inEntry 14 }

gtDVBS2inCodeRate OBJECT-TYPE
	SYNTAX INTEGER { auto(1), c1x2(500), c3x5(600), c2x3(666), c3x4(750), c4x5(800), c5x6(833), c7x8(875), c8x9(888), c9x10(900) }
	MAX-ACCESS read-write
	STATUS current
	DESCRIPTION
		"The gtDVBS2inCodeRate entity represent the coding rate
		of a DVB-S2 input stream within the GT01/GN50 rack unit."
::= { gtDVBS2inEntry 15 }

gtDVBS2inLNBType OBJECT-TYPE
	SYNTAX INTEGER { none(1), universal(2), fixed(3) }
	MAX-ACCESS read-write
	STATUS current
	DESCRIPTION
		"The gtDVBS2inLNBType entity represent the LNB voltage setting
		of a DVB-S2 input stream within the GT01/GN50 rack unit."
::= { gtDVBS2inEntry 20 }

gtDVBS2inLOFrequency OBJECT-TYPE
	SYNTAX Unsigned32
	UNITS "kHz"
	MAX-ACCESS read-write
	STATUS current
	DESCRIPTION
		"The gtDVBS2inLOFrequency entity represent the LO frequency
		of a DVB-S2 input stream within the GT01/GN50 rack unit.
		This parameter is only used if LNB is set to fixed."
::= { gtDVBS2inEntry 21 }

gtDVBS2inLNBVoltage OBJECT-TYPE
	SYNTAX INTEGER { auto(1), off(2), lnb13V(13), lnb18V(18) }
	MAX-ACCESS read-write
	STATUS current
	DESCRIPTION
		"The gtDVBS2inLNBVoltage entity represent the LNB voltage setting
		of a DVB-S2 input stream within the GT01/GN50 rack unit."
::= { gtDVBS2inEntry 22 }

gtDVBS2in22kHzTone OBJECT-TYPE
	SYNTAX INTEGER { auto(1), off(2), on(3) }
	MAX-ACCESS read-write
	STATUS current
	DESCRIPTION
		"The gtDVBS2in22kHzTone entity represent the LNB 22 kHz tone setting
		of a DVB-S2 input stream within the GT01/GN50 rack unit."
::= { gtDVBS2inEntry 23 }

gtDVBS2inDiSEqCType OBJECT-TYPE
	SYNTAX INTEGER { none(1), diseqc4way(4) }
	MAX-ACCESS read-write
	STATUS current
	DESCRIPTION
		"The gtDVBS2inDiSEqCType entity represent the DiSEqC type setting
		of a DVB-S2 input stream within the GT01/GN50 rack unit."
::= { gtDVBS2inEntry 24 }

gtDVBS2inDiSEqCSource OBJECT-TYPE
	SYNTAX Unsigned32
	UNITS "source"
	MAX-ACCESS read-write
	STATUS current
	DESCRIPTION
		"The gtDVBS2inDiSEqCSource entity represent the DiSEqC source id
		of a DVB-S2 input stream within the GT01/GN50 rack unit.
		This parameter is only used if gtDVBS2inDiSEqCType is
		set to other than none."
::= { gtDVBS2inEntry 25 }

--============================================================================--
END
